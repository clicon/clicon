module datamodel{
    list a{
        key "x"; 
	leaf x{
	    type string;
	}
	leaf k {
	    type string;
	}
	container b{
	    leaf y{
		type string;
	    }
	}
	list c{
	    key "z";
	    leaf z{
		type string;
	    }
	}
    }
}
