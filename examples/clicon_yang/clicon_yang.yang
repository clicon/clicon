module datamodel{
    list a{
        key "x"; 
	leaf x{
	    type string;
	}
	leaf k {
	    type string;
	}
	container b{
	    leaf y{
		type string;
	    }
	}
	container c{
	    leaf z{
		type string;
	    }
	}
    }
}
