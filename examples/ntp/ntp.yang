module ntp { // In CLIgen, this datamodel will be called datamodel:ntp
     prefix ntp;

     organization
       "CLICON";

     description
       "This module contains a YANG definitions for CLICON NTP
        Copyright (c) 2009-2015 Olof Hagsand and Benny Holmgren.
        All rights reserved.";

     revision 2014-06-26 {
       description
         "Initial revision.";
     }

     container ntp{
        description "Network Time Protocol";
        container logging{
           description "Configure NTP message logging";
	   leaf status{
	       type boolean;
           }
        }
	list server{
           description "Configure NTP Server";
	   key ipv4addr; 
	   leaf ipv4addr{
	      description "IPv4 address of peer";
	      type ipv4-address; /* see RFC 6991 */
           }
        }
    }
}
